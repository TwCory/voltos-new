module voltos-main {
    yang-version 1.1;
    namespace "http://coralt.org/ns/yang/voltos-main";
    prefix voltos;


    import ietf-inet-types {
        prefix inet;
    }

    organization
        "Coralt Networks";
    contact
        "Coralt Networks
         
         User List:         <mailto:user-group@coralt.org>
         Developer List:    <mailto:dev-group@coralt.org>
         
         Documentation:     http://docs.coralt.org/voltos";
    description
        "Core/System Main YANG Module for VoltOS
         Copyright (C) 2025 Coralt Networks
         MIT License In Use.";

    revision 2025-09-06 {
        description
            "Initial revision";
    }

    container main {
        container default {
            description
                "Set a command to its defaults";
        }
        container bfd {
            description
                "BFD configuration commands";
        }
        leaf version {
            description
                "Version";
            type string;
        }

        leaf boot-start-marker {
            type empty;
        }
        container boot {
            description
                "Modify the boot system parameters";
            container system {
                description
                    "System Image";
                leaf tftp-path {
                    description
                        "Example: 192.168.x.x/<path-to-image>";
                    type string;
                }
                leaf tftp {
                    description
                        "Example: 192.168.x.x/<path-to-image>";
                    type string;
                }
                container bootfile {
                    description
                        "WORD - Boot File Name";
                    list file-list-ordered-by-user {
                        ordered-by user;
                        key "filename";
                        leaf filename {
                            description
                                "WORD - TFTP File Name or URL";
                            type string;
                        }
                    }
                }
                container flash {
                    description
                        "Flash - Boot from Flash Memory";
                    list flash-list-ordered-by-user {
                        ordered-by user;
                        key "flash-leaf";
                        leaf flash-leaf {
                            type string;
                        }
                    }
                }
            }
        }

        leaf boot-end-marker {
            type empty;
        }

        leaf hostname {
            description
                "Set the system's network name";
            type string {
                length "1..246";
                pattern '([0-9.]*[A-Za-z\-_]+[A-Za-z0-9.\-_]*)';
            }
            default "router";
        }
        container l2 {
            description
                "Layer 2 configuration";
            leaf router-id {
                description
                    "Configure layer 2 identifier";
                type inet:ipv4-address;
            }
        }

    }
}
